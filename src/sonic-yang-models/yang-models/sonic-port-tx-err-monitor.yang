module sonic-port-tx-err-monitor {

    yang-version 1.1;

    namespace "http://github.com/sonic-net/sonic-port-tx-err-monitor";
    prefix port-tx-err-monitor;

    description "Port TX error monitor configuration in SONiC OS";

    revision 2026-02-24 {
        description "First Revision";
    }

    container sonic-port-tx-err-monitor {

        container PORT_TX_ERR_MONITOR {

            description "PORT_TX_ERR_MONITOR part of config_db.json";

            container CONFIG {

                leaf threshold {
                    description "Maximum acceptable TX error delta within the evaluation window";
                    type uint64 {
                        range "1..max";
                    }
                }

                leaf window_sec {
                    description "Evaluation time window in seconds";
                    type uint32 {
                        range "1..86400";
                    }
                }

                leaf enabled {
                    description "Enable or disable TX error monitoring";
                    type enumeration {
                        enum enabled;
                        enum disabled;
                    }
                }

            }
            /* end of container CONFIG */
        }
        /* end of container PORT_TX_ERR_MONITOR */
    }
    /* end of top level container */
}
